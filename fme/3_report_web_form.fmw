FME workspace 3_report_web_form.fmw

Parameters:
- SourceDataset_TEXTLINE = Z:\DonStuff\DemoData\2013Demos\AlertReportingSystem\2ndIteration\data\reporter_data\web_report_polygon_data.txt   # Source Text File(s)
- URL = https://fmepedia2014-safe-software.fmecloud.com
- USERNAME = fmepediademos
- PASSWORD =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

Readers:
- TEXTLINE_1: TEXTLINE from $(SourceDataset_TEXTLINE)

Writers:
- GOOGLEFUSIONTABLES_1: GOOGLEFUSIONTABLES in LL84
- GOOGLEFUSIONTABLES_2: GOOGLEFUSIONTABLES

text_line (reader TEXTLINE_1)
    attributes: text_line_data buffer
    -> AttributeTrimmer
Logger_2
    MESSAGE = Feature is:
    MAXFEATS = 20
    MAXCOORDS = 20
EMSLocationReport (writer GOOGLEFUSIONTABLES_2)
    attributes: content text, datetime datetime, email_reporter text, report_type text, subject text, url text, latitude number, longitude number

Bookmark: Expand JSON and Expose
AttributeTrimmer
    SRC_ATTRS = text_line_data
    TRIM_CHARS = "
    TRIM_TO_NONE = Yes
    TRIM_TYPE = Both
    -> JSONFlattener
JSONFlattener
    RECURSIVE = Yes
    JSON_ATTR = text_line_data
    -> AttributeExposer
AttributeExposer
    ATTR_LIST = description,email,extremity,radius,title,url,wkt
    -> GeometryReplacer

Bookmark: WKT-FME Geometry
GeometryReplacer
    ATTR = wkt
    KIND_LONG = OGC Well Known Text
    -> CoordinateExtractor
CoordinateExtractor
    Y_ATTR = latitude
    X_ATTR = longitude
    Z_DEFAULT = -9999
    Z_ATTR = _z
    IND = 0
    -> CoordinateSystemSetter
CoordinateSystemSetter
    COORDSYS = LL84
    -> TimeStamper

Bookmark: Generate timestamp and Report Type
TimeStamper
    FMT = FME Date/Time (^Y^m^d^H^M^S)
    TIME_ATTR = datetime
    -> StringConcatenator
StringConcatenator
    PARM_LINE = Web Report - Severity(@Value(extremity))
    VAL_ATTR = report_type
    -> StringConcatenator_3
    -> EMSLocationReport (writer GOOGLEFUSIONTABLES_2)

Bookmark: Trigger Downstream Event - ems_new_data_logged
StringConcatenator_3
    PARM_LINE:
      {
      "report_type": "@Value(report_type)",
      "email_from": "@Value(email)",
      "url": "@Value(url)",
      "latitude": "@Value(latitude)",
      "longitude": "@Value(longitude)",
      "datetime": "@Value(datetime)",
      "subject": "@Value(title)",
      "content":"@Value(description)"
      }
    VAL_ATTR = email_content
    -> FMEServerNotifier
FMEServerNotifier
    PASSWORD = $(PASSWORD)
    USERNAME = $(USERNAME)
    BODY = @Value(email_content)
    TOPIC = ems_new_data_logged
    URL = $(URL)
    -> Logger_2
    <REJECTED> -> Logger_2
