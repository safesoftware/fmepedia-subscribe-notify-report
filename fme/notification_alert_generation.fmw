FME workspace notification_alert_generation.fmw

Parameters:
- SourceDataset_TEXTLINE = Z:\DonStuff\DemoData\2013Demos\AlertReportingSystem\2ndIteration\data\notification_data\notification_report2.json   # Source Text File(s)

Readers:
- TEXTLINE_1: TEXTLINE from $(SourceDataset_TEXTLINE)
- GOOGLEFUSIONTABLES_1: GOOGLEFUSIONTABLES

Writers:
- NULL_1: NULL

Note: text_line
text_line (reader TEXTLINE_1)
    attributes: text_line_data buffer
    -> JSONFlattener
JSONFlattener
    RECURSIVE = Yes
    JSON_ATTR = text_line_data
    -> AttributeExposer
AttributeExposer
    ATTR_LIST = content,datetime,email_from,latitude,longitude,report_type,subject,url
    -> 2DPointAdder
2DPointAdder
    YVALATTR = @Value(latitude)
    XVALATTR = @Value(longitude)
    -> StringConcatenator_2
StringConcatenator_2
    PARM_LINE = http://maps.google.com/maps/api/staticmap?center=@Value(latitude),@Value(longitude)&zoom=13&markers=@Value(latitude),@Value(longitude)&size=500x300&sensor=false
    VAL_ATTR = staticmapURL
    -> HTTPFetcher
HTTPFetcher
    STATUS_CODE_ATTR = _http_status_code
    USE_COOKIES = No
    URL = @Value(staticmapURL)
    VAL_ATTR = staticmapimage
    SAVED_HEADERS_ATTR = _headers
    CONTINUE_ON_ERROR = No
    USE_HEADER_ENCODING = No
    HTTP_AUTH_METHOD = Basic
    HTTP_PROXY_AUTH_METHOD = Basic
    -> UUIDGenerator
UUIDGenerator
    UUID_ATTR = _uuid
    -> StringConcatenator_3
StringConcatenator_3
    PARM_LINE = c:/ems_temp/@Value(_uuid).jpg
    VAL_ATTR = filename
    -> AttributeFileWriter
AttributeFileWriter
    FILE_NAME = @Value(filename)
    SOURCE_ATTR = staticmapimage
    CHAR_ENCODING = fme-system
    -> SpatialFilter [input 1]
    -> SpatialFilter_2 [input 1]
Note: EMSActiveSubscriptions
EMSActiveSubscriptions (reader GOOGLEFUSIONTABLES_1)
    attributes: geom location, email text, request_id text, request_time text, enddate text, startdate text, twitter text, query_type text
    -> TestFilter
TestFilter
    TEST_LIST = BOOL_OP,OR,COMPOSITE_TEST,<Unused>,TEST_CLAUSE,"TEST ""@Value(query_type)"" = ""inside""",INSIDE_AREA_ALERT,BOOL_OP,OR,COMPOSITE_TEST,<Unused>,TEST_CLAUSE,"TEST ""@Value(query_type)"" = ""outside""",OUTSIDE_AREA_ALERT
    INSIDE_AREA_ALERT -> SpatialFilter [input 2]
    OUTSIDE_AREA_ALERT -> SpatialFilter_2 [input 2]
SpatialFilter
    USE_BOUNDING_BOX = For CANDIDATES Only
    PREDATTR = _predicate
    BASE_TYPE = Single Base
    PREDICATES = INTERSECTS
    MERGE_ATTRS = Yes
    PASS_CRITERIA = Pass Against One Base
    CURVE_BOUNDARY_RULE_PARAM = Default Rule
    PASSED -> StringConcatenator
SpatialFilter_2
    USE_BOUNDING_BOX = For CANDIDATES Only
    PREDATTR = _predicate
    BASE_TYPE = Single Base
    PREDICATES = DISJOINT
    MERGE_ATTRS = Yes
    PASS_CRITERIA = Pass Against One Base
    CURVE_BOUNDARY_RULE_PARAM = Default Rule
    PASSED -> StringConcatenator
StringConcatenator
    PARM_LINE:
      {
      email_to:@Value(email),
      email_subject: "Notification Alert - @Value(report_type)",
      email_attachment: "@Value(filename)",
      subscriber_content: "There has been a @Value(report_type) event.  The event has the following associated information: \r\nSubject:  @Value(subject) \r\n Content: @Value(content) \r\nURL: @Value(url)\r\n \r\n Map showing all photos logged is here: https://www.google.com/fusiontables/DataSource?snapid=S423487zYjn \r\n\r\nMap showing all events logged is here: https://www.google.com/fusiontables/DataSource?snapid=S429077Mdcg \r\n \r\n \r\n ----  UNSUBSCRIBE  ----- \r\n\r\nTo unsubscribe to these notifications click the link below.  \r\nhttp://alertdemo.safe.com/fmejobsubmitter/EEMS/subscription_delete.fmw?opt_servicemode=async&subscriber_id=@Value(request_id)&email_address=@Value(email) \r\n\r\n Image showing report location is attached below: \r\n\r\n",
      apple_content:"@Value(report_type) | @Value(subject)  - @Value(content) | @Value(latitude), @Value(longitude)"
      }
    VAL_ATTR = subscription_request
    -> FMEServerNotifier
FMEServerNotifier
    STATUS_CODE_ATTR = _http_status_code
    URL = http://localhost
    HTTP_AUTH_PASSWORD = admin
    TOPIC = ems_notification_alert
    HTTP_AUTH_USERNAME = admin
    HTTP_UPLOAD_BODY = subscription_request
    HTTP_UPLOAD_CONTENT_TYPE = text/plain
