FME workspace 1_subscription_request.fmw

Parameters:
- SourceDataset_TEXTLINE = Z:\DonStuff\DemoData\2013Demos\AlertReportingSystem\2ndIteration\data\subscriber_data\subscription_point_request.txt   # Source Text File(s)
- SERVER_URL_HTML = http://demos.fmeserver.com/subscribe-notify-report/subscriber.html   # Server URL (alertdemo http directory)
- HTTP_AUTH_USERNAME = fmepediademos   # Username
- HTTP_AUTH_PASSWORD =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   # Password
- URL = https://fmepedia2014-safe-software.fmecloud.com   # Web Connection URL

Readers:
- TEXTLINE_1: TEXTLINE from $(SourceDataset_TEXTLINE)

Writers:
- GOOGLEFUSIONTABLES_1: GOOGLEFUSIONTABLES

text_line (reader TEXTLINE_1)
    attributes: text_line_data buffer
    -> AttributeTrimmer
Logger_2
    MESSAGE = Feature is:
    MAXFEATS = 20
    MAXCOORDS = 20
EMSSubscriptionRequest (writer GOOGLEFUSIONTABLES_1)
    attributes: email text, enddate datetime, request_id text, request_time datetime, startdate datetime, wkt text, query_type text

Bookmark: Process JSON request
AttributeTrimmer
    SRC_ATTRS = text_line_data
    TRIM_CHARS = "
    TRIM_TO_NONE = Yes
    TRIM_TYPE = Both
    -> JSONFlattener
JSONFlattener
    RECURSIVE = Yes
    JSON_ATTR = text_line_data
    -> AttributeExposer
AttributeExposer
    ATTR_LIST = email,wkt,enddate,startdate,twitter,area_type,radius
    -> UUIDGenerator

Bookmark: Generate Unique ID & Timestamp
UUIDGenerator
    UUID_ATTR = request_id
    -> TimeStamper
TimeStamper
    FMT = FME Date/Time (^Y^m^d^H^M^S)
    TIME_ATTR = request_time
    -> SubstringExtractor

Bookmark: Get All Dates Consistent
SubstringExtractor
    RESULT_ATTR = startdate
    SRC_ATTR = startdate
    START = 0
    END = 9
    -> SubstringExtractor_2
SubstringExtractor_2
    RESULT_ATTR = enddate
    SRC_ATTR = enddate
    START = 0
    END = 9
    -> DateFormatter
DateFormatter
    DATE_ATTR = request_time
    FMT = XML DateTime (%Y-%m-%dT%H:%M:%S)
    -> EMSSubscriptionRequest (writer GOOGLEFUSIONTABLES_1)
    -> FMEServerEmailGenerator

Bookmark: Send Confirmation Email
FMEServerEmailGenerator
    email_replyto = subscribe-confirm-email@fmepedia2014-safe-software.fmecloud.com
    email_subject = FMEpedia demos: Request to subscribe to receive alerts <REQUEST_ID:@Value(request_id)>
    email_to = @Value(email)
    email_subscriber_content:
      <p>You  requested to receive notifcation alerts from $(SERVER_URL_HTML) at @Value(request_time). </p>
      <p>The details of the request are as follows: </p>
      <ul>
      <li>Email:@Value(email)</li>
      <li>StartDate: @Value(startdate) </li>
      <li>EndDate: @Value(enddate)</li>
      <li>QueryType:@Value(area_type)</li>
      </ul>
      <br>
      <p><b>If this is correct then reply to this email</b> from the email address it was addressed to.</p>
      <br>
      If you did not want to be sent alerts then simply ignore this email.
      <br>
      -----------DO NOT EDIT-----------
    -> FMEServerNotifier_2
FMEServerNotifier_2
    PASSWORD = $(HTTP_AUTH_PASSWORD)
    USERNAME = $(HTTP_AUTH_USERNAME)
    BODY = @Value(text_line_data)
    TOPIC = ems_subscribe_confirm_email
    URL = $(URL)
    -> Logger_2
    <REJECTED> -> Logger_2

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_to =   # To
- email_cc =   # CC
- email_from =   # From
- email_replyto =   # Reply to
- email_subject =   # Subject
- email_subscriber_content =   # Message
- email_attachment_paths =   # Attachments (comma separated)

INPUT (input)
    -> Counter
Counter
    SCOPE = Local
    START = 0
    DOMAIN = counter
    CNT_ATTR = _email_feature_id
    -> ParameterFetcher
ParameterFetcher
    ATTR_LIST = _email_from {$(email_from)} _email_replyto {$(email_replyto)} _email_attachment_paths {$(email_attachment_paths)} _email_cc {$(email_cc)}
    -> AttributeCreator
AttributeCreator
    NUM_PRIOR_FEATURES = 0
    NUM_SUBSEQUENT_FEATURES = 0
    ATTR_LIST = _email_to,$(email_to),_email_subject,$(email_subject),_email_subscriber_content,$(email_subscriber_content)
    -> JSONTemplater
JSONTemplater
    RESULT_ATTRIBUTE = text_line_data
    CONSECUTIVE_GROUPS = No
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    VISIBLE_QUERY_VALIDATE = Yes
    -> Tester
Tester
    TEST_MODE = Automatic
    TEST_DESCRIPTION = ""
    BOOL_OP = OR
    TEST_CLAUSE = TEST _email_attachment_paths ATTRIBUTE_IS_EMPTY <Unused>
    PASSED -> OUTPUT (output)
    FAILED -> AttributeSplitter
OUTPUT (output)

Bookmark: Add the attachments
AttributeSplitter
    LIST_NAME = _email_attachment_path_list
    ATTR_NAME = _email_attachment_paths
    DELIMITER = ,
    TRIM_OPTION = Both
    DROP_EMPTY_PARTS = No
    -> ListExploder
ListExploder
    INDEX_ATTR = _element_index
    MODE = List Elements and Original Attributes
    LIST_ATTR = _email_attachment_path_list{}
    LIST_FOUND -> StringConcatenator
StringConcatenator
    PARM_LINE = "email_attachment{@Value(_element_index)}": "@Value(_email_attachment_path_list)"
    VAL_ATTR = _email_attachment_json
    -> Aggregator
Aggregator
    GROUP_BY = _email_feature_id
    MODE = Assemble One Level
    ACCUM_ATTRS_NAME = Yes
    SEP = ,
    AGGREGATE_TYPE = Homogeneous Collection (If Possible)
    CONCAT_ATTRS = _email_attachment_json
    ORDERED = No
    AGGREGATE -> StringReplacer_2
StringReplacer_2
    SRC_ATTRS = _email_attachment_json
    REGEXP = no
    CASE = no
    REPLACE_TEXT = \\
    NO_MATCH = _FME_NO_OP_
    FIND_TEXT = \
    -> StringReplacer
StringReplacer
    SRC_ATTRS = text_line_data
    REGEXP = no
    CASE = no
    REPLACE_TEXT:
      ,
      @Value(_email_attachment_json)
      }
    NO_MATCH = _FME_NO_OP_
    FIND_TEXT = }
    -> OUTPUT (output)
