FME workspace 4_notification_alert_generation.fmw

Parameters:
- SourceDataset_TEXTLINE = Z:\DonStuff\DemoData\2013Demos\AlertReportingSystem\2ndIteration\data\notification_data\notification_report2.json   # Source Text File(s)
- URL = https://fmepedia2014-safe-software.fmecloud.com
- REPOSITORY = Subscribe%20Report%20Notify   # Repository
- HTTP_AUTH_USERNAME = fmepediademos
- HTTP_AUTH_PASSWORD =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

Readers:
- TEXTLINE_1: TEXTLINE from $(SourceDataset_TEXTLINE)
- GOOGLEFUSIONTABLES_1: GOOGLEFUSIONTABLES

Writers:
- NULL_1: NULL

Note: text_line
text_line (reader TEXTLINE_1)
    attributes: text_line_data buffer
    -> JSONFlattener
2DPointAdder
    XVALATTR = @Value(longitude)
    YVALATTR = @Value(latitude)
    -> StringConcatenator_2
EMSActiveSubscriptions (reader GOOGLEFUSIONTABLES_1)
    attributes: <Unused> location, email text, enddate text, request_id text, request_time text, startdate text, query_type text
    -> TestFilter
TestFilter
    TEST_LIST = BOOL_OP,OR,COMPOSITE_TEST,<Unused>,TEST_CLAUSE,"TEST ""@Value(query_type)"" = ""inside""",INSIDE_AREA_ALERT,BOOL_OP,OR,COMPOSITE_TEST,<Unused>,TEST_CLAUSE,"TEST ""@Value(query_type)"" = ""outside""",OUTSIDE_AREA_ALERT
    DEFAULT_VALUE = <UNFILTERED>
    INSIDE_AREA_ALERT -> SpatialFilter [input 2]
    OUTSIDE_AREA_ALERT -> SpatialFilter_2 [input 2]

Bookmark: Extract JSON
JSONFlattener
    RECURSIVE = Yes
    JSON_ATTR = text_line_data
    -> AttributeExposer
AttributeExposer
    ATTR_LIST = content,datetime,email_from,latitude,longitude,report_type,subject,url
    -> 2DPointAdder

Bookmark: Generate static map
StringConcatenator_2
    PARM_LINE = http://maps.google.com/maps/api/staticmap?center=@Value(latitude),@Value(longitude)&zoom=13&markers=@Value(latitude),@Value(longitude)&size=500x300&sensor=false
    VAL_ATTR = staticmapURL
    -> HTTPFetcher
HTTPFetcher
    VAL_ATTR = staticmapimage
    USE_HEADER_ENCODING = No
    USE_COOKIES = No
    STATUS_CODE_ATTR = _http_status_code
    SAVED_HEADERS_ATTR = _headers
    HTTP_AUTH_METHOD = Basic
    URL = @Value(staticmapURL)
    CONTINUE_ON_ERROR = No
    HTTP_PROXY_AUTH_METHOD = Basic
    -> UUIDGenerator_2
UUIDGenerator_2
    UUID_ATTR = _uuid
    -> StringConcatenator_4
StringConcatenator_4
    PARM_LINE = @Value(_uuid).jpg
    VAL_ATTR = filename
    -> AttributeCreator
AttributeCreator
    ATTR_LIST = filename,$(FME_SHAREDRESOURCE_TEMP)@Value(filename)
    -> AttributeFileWriter_2
AttributeFileWriter_2
    OVERWRITE_FILE = Overwrite file
    CHAR_ENCODING = fme-binary
    FILE_NAME = @Value(filename)
    SOURCE_ATTR = staticmapimage
    -> SpatialFilter [input 1]
    -> SpatialFilter_2 [input 1]

Bookmark: Trigger when report overlaps area of interest
SpatialFilter
    USE_BOUNDING_BOX = For CANDIDATES Only
    MERGE_ATTRS = Yes
    BASE_TYPE = Single Base
    PASS_CRITERIA = Pass Against One Base
    PREDATTR = _predicate
    PREDICATES = INTERSECTS
    CURVE_BOUNDARY_RULE_PARAM = Default Rule
    PASSED -> FMEServerEmailGenerator

Bookmark: Trigger when report is outside area of interest
SpatialFilter_2
    USE_BOUNDING_BOX = For CANDIDATES Only
    MERGE_ATTRS = Yes
    BASE_TYPE = Single Base
    PASS_CRITERIA = Pass Against One Base
    PREDATTR = _predicate
    PREDICATES = DISJOINT
    CURVE_BOUNDARY_RULE_PARAM = Default Rule
    PASSED -> FMEServerEmailGenerator

Bookmark: Send Confirmation Email
FMEServerEmailGenerator
    email_subject = Notification Alert - @Value(report_type)
    email_to = @Value(email)
    email_subscriber_content:
      <b>There has been a new event in the area you subscribed to.</b>

      <p>The event has the following associated information:</p>

      <ul>
      <li>Severity:  @Value(report_type)</li>
      <li>Subject:  @Value(subject)</li>
      <li>Content: @Value(content)</li>
      <li>URL: @Value(url)</li>
      </ul>

      <p>Map showing all reports logged is <a href="https://www.google.com/fusiontables/embedviz?q=select+col0+from+1hN5hAIbHnu8MoUCIWbBnfgA9op3n_kLGvWi8czdk&viz=MAP&h=false&lat=38.822590976177075&lng=-42.5390625&t=1&z=3&l=col0&y=2&tmplt=2&hml=KML">here.</a></p>

      <p>Image showing report location is attached below.</p>

      ----  UNSUBSCRIBE  -----

      <p>To unsubscribe to these notifications click the link below.</p>

      $(URL)/fmejobsubmitter/$(REPOSITORY)/subscription_delete.fmw?opt_servicemode=async&subscriber_id=@Value(request_id)&email_address=@Value(email)
    email_attachment_paths = @Value(filename)
    -> FMEServerNotifier_2
FMEServerNotifier_2
    PASSWORD = $(HTTP_AUTH_PASSWORD)
    USERNAME = $(HTTP_AUTH_USERNAME)
    BODY = @Value(text_line_data)
    TOPIC = ems_subscribe_notification_alert
    URL = $(URL)

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_to =   # To
- email_cc =   # CC
- email_from =   # From
- email_replyto =   # Reply to
- email_subject =   # Subject
- email_subscriber_content =   # Message
- email_attachment_paths =   # Attachments (comma separated)

INPUT (input)
    -> Counter
Counter
    SCOPE = Local
    START = 0
    DOMAIN = counter
    CNT_ATTR = _email_feature_id
    -> ParameterFetcher
ParameterFetcher
    ATTR_LIST = _email_from {$(email_from)} _email_replyto {$(email_replyto)} _email_attachment_paths {$(email_attachment_paths)} _email_cc {$(email_cc)}
    -> AttributeCreator
AttributeCreator
    NUM_PRIOR_FEATURES = 0
    NUM_SUBSEQUENT_FEATURES = 0
    ATTR_LIST = _email_to,$(email_to),_email_subject,$(email_subject),_email_subscriber_content,$(email_subscriber_content)
    -> JSONTemplater
JSONTemplater
    RESULT_ATTRIBUTE = text_line_data
    CONSECUTIVE_GROUPS = No
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    VISIBLE_QUERY_VALIDATE = Yes
    -> Tester
Tester
    TEST_MODE = Automatic
    TEST_DESCRIPTION = ""
    BOOL_OP = OR
    TEST_CLAUSE = TEST _email_attachment_paths ATTRIBUTE_IS_EMPTY <Unused>
    PASSED -> OUTPUT (output)
    FAILED -> AttributeSplitter
OUTPUT (output)

Bookmark: Add the attachments
AttributeSplitter
    LIST_NAME = _email_attachment_path_list
    ATTR_NAME = _email_attachment_paths
    DELIMITER = ,
    TRIM_OPTION = Both
    DROP_EMPTY_PARTS = No
    -> ListExploder
ListExploder
    INDEX_ATTR = _element_index
    MODE = List Elements and Original Attributes
    LIST_ATTR = _email_attachment_path_list{}
    LIST_FOUND -> StringConcatenator
StringConcatenator
    PARM_LINE = "email_attachment{@Value(_element_index)}": "@Value(_email_attachment_path_list)"
    VAL_ATTR = _email_attachment_json
    -> Aggregator
Aggregator
    GROUP_BY = _email_feature_id
    MODE = Assemble One Level
    ACCUM_ATTRS_NAME = Yes
    SEP = ,
    AGGREGATE_TYPE = Homogeneous Collection (If Possible)
    CONCAT_ATTRS = _email_attachment_json
    ORDERED = No
    AGGREGATE -> StringReplacer_2
StringReplacer_2
    SRC_ATTRS = _email_attachment_json
    REGEXP = no
    CASE = no
    REPLACE_TEXT = \\
    NO_MATCH = _FME_NO_OP_
    FIND_TEXT = \
    -> StringReplacer
StringReplacer
    SRC_ATTRS = text_line_data
    REGEXP = no
    CASE = no
    REPLACE_TEXT:
      ,
      @Value(_email_attachment_json)
      }
    NO_MATCH = _FME_NO_OP_
    FIND_TEXT = }
    -> OUTPUT (output)
