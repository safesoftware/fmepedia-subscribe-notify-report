FME workspace 2_subscription_confirm_email.fmw

Parameters:
- SourceDataset_TEXTLINE = Z:\DonStuff\DemoData\2013Demos\AlertReportingSystem\2ndIteration\data\subscriber_data\subscribe_confirm_email.txt   # Source Text File(s)
- SERVER_URL_HTML = http://demos.fmeserver.com/subscribe-notify-report/
- URL = https://fmepedia2014-safe-software.fmecloud.com   # Web Connection URL
- repository_name = Subscribe%20Report%20Notify   # Repository Name
- HTTP_AUTH_PASSWORD =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
- HTTP_AUTH_USERNAME = fmepediademos   # HTTP_AUTH_USERNAMEHTTP_AUTH_USERNAME

Readers:
- TEXTLINE_1: TEXTLINE from $(SourceDataset_TEXTLINE)
- GOOGLEFUSIONTABLES_DB_1: GOOGLEFUSIONTABLES_DB

Writers:
- GOOGLEFUSIONTABLES_1: GOOGLEFUSIONTABLES

text_line (reader TEXTLINE_1)
    attributes: text_line_data buffer
    -> JSONFlattener
EMSSubscriptionRequest (reader GOOGLEFUSIONTABLES_DB_1)
    attributes: geom location, email text, enddate text, request_id text, request_time text, startdate text, wkt text, query_type text
    -> InlineQuerier_2 [input 2]
EMSActiveSubscriptions (writer GOOGLEFUSIONTABLES_1)
    attributes: email text, enddate datetime, request_id text, request_time datetime, startdate datetime, query_type text
Note: EMSFutureSubscriptions
EMSFutureSubscriptions (writer GOOGLEFUSIONTABLES_1)
    attributes: email text, enddate datetime, request_id text, request_time datetime, startdate datetime, query_type text
Note: EMSSubscriptionRequest / Request handled so delete.
EMSSubscriptionRequest (writer GOOGLEFUSIONTABLES_1)
    attributes: email text, wkt text, request_id text, request_time text, enddate text, startdate text, query_type text

Bookmark: Parse Email Request
JSONFlattener
    RECURSIVE = Yes
    JSON_ATTR = text_line_data
    -> AttributeExposer_2
AttributeExposer_2
    ATTR_LIST = email_publisher_attachment{},email_publisher_to,email_publisher_received,email_publisher_subject,email_publisher_from,email_publisher_sent
    -> StringSearcher

Bookmark: Get Confirmation ID
StringSearcher
    REGEXP = <REQUEST_ID:.*>
    CASE = no
    ATTRIBUTE = email_publisher_subject
    MATCHED -> SubstringExtractor
SubstringExtractor
    RESULT_ATTR = request_id
    SRC_ATTR = _matched_characters
    START = 12
    END = -2
    -> InlineQuerier_2 [input 1]

Bookmark: Now Verify that the email,id combination is valid
  Replace with FeatureReader
InlineQuerier_2
    QUERY_SCHEMA = Matched,request_id,varchar(30),email_publisher_from,varchar(30),subscription_confirmation.fme_feature_content,fme_feature_content,email,varchar(30),subscription_request.fme_feature_content,fme_feature_content
    TABLE_DEF = subscription_confirmation,request_id,varchar(30),email_publisher_from,varchar(30),subscription_request,request_id,varchar(30),email,varchar(30)
    QUERY_DEF:
      Matched,SELECT *
      FROM subscription_confirmation,
           subscription_request
      WHERE   subscription_request.email      =  subscription_confirmation.email_publisher_from AND
              subscription_request.request_id =  subscription_confirmation.request_id,FIRST
    Matched -> GeometryReplacer

Bookmark: BuildGeometry
GeometryReplacer
    ATTR = wkt
    KIND_LONG = OGC Well Known Text
    -> CoordinateSystemSetter
CoordinateSystemSetter
    COORDSYS = LL84
    -> TimeStamper

Bookmark: SetupTimeBand
TimeStamper
    FMT = FME Date (^Y^m^d)
    TIME_ATTR = current_date
    -> DateFormatter
DateFormatter
    DATE_ATTR = enddate,startdate
    FMT = FME Date (%Y%m%d)
    -> TestFilter
    -> FMEServerEmailGenerator
TestFilter
    TEST_LIST:
      BOOL_OP,AND,COMPOSITE_TEST,<Unused>,TEST_CLAUSE,"TEST ""@Value(startdate)"" <= ""@Value(current_date)""
      TEST ""@Value(enddate)"" >= ""@Value(current_date)""",Active,BOOL_OP,OR,COMPOSITE_TEST,<Unused>,TEST_CLAUSE,"TEST ""@Value(startdate)"" > ""@Value(current_date)""",Future
    DEFAULT_VALUE = <UNFILTERED>
    Active -> EMSActiveSubscriptions (writer GOOGLEFUSIONTABLES_1)
    Future -> EMSFutureSubscriptions (writer GOOGLEFUSIONTABLES_1)
    Future -> EMSSubscriptionRequest (writer GOOGLEFUSIONTABLES_1)
    Active -> EMSSubscriptionRequest (writer GOOGLEFUSIONTABLES_1)
    <UNFILTERED> -> EMSSubscriptionRequest (writer GOOGLEFUSIONTABLES_1)

Bookmark: Send Confirmation Email
FMEServerEmailGenerator
    email_subject = FMEpedia demo: FME Server alert request has been activated
    email_to = @Value(email)
    email_from = subscribe-reprt-notify-demo@fmepedia2014-safe-software.fmecloud.com
    email_subscriber_content:
      <p>You  are now registered to receive notifcation alerts from $(SERVER_URL_HTML)index.html at @Value(request_time). </p>

      <p>The details of the request are as follows:

      <ul>
      <li>email:@Value(email)</li>
      <li>StartDate: @Value(startdate)</li>
      <li>EndDate: @Value(enddate)</li>
      <li>QueryType:@Value(query_type)</li>

      <br>
      ----  UNSUBSCRIBE  -----

      <p>To unsubscribe to these notifications click the link below.</p>

      $(URL)/fmejobsubmitter/$(repository_name)/subscription_delete.fmw?opt_servicemode=async&subscriber_id=@Value(request_id)&email_address=@Value(email)
    -> FMEServerNotifier_2
Note: EMSActiveSubscriptions
FMEServerNotifier_2
    PASSWORD = $(HTTP_AUTH_PASSWORD)
    USERNAME = $(HTTP_AUTH_USERNAME)
    BODY = @Value(text_line_data)
    TOPIC = ems_subscribe_activated
    URL = $(URL)

FME custom transformer FMEServerEmailGenerator
This transformer provides an easy method for creating an email message to be sent by the FME Server Notification Service.
1. Create Topic and Email Subscriber
In the FME Server Web Interface, create a topic for notifications to be sent to and also create a email subscriber that subscribes to this topic.
2. Create a Workspace 
Once you file out the the email fields in the transformer you can send the email message in two different ways:
A. Send an email when the workspace completes
add a text file writer to the workspace
connect this transformer to the text file writer's feature type
publish the workspace
register it with the Job Submitter, Data Download and/or Notification Service
for each service, click the edit button
for Topics to Publish (Success), select the topic you created earlier
for Notification Writer, select the text file writer you added eariler
finish publishing the workspace
now the workspace will send an email whenever it is run through the FME Server Service you registered it with.
B. Send an email using a transformer
add a FMEServerNotifier transformer to your workflow
configure it to publish to the topic that you created earlier
for Content, select the text_line_data attribute
now the workspace will send an email whenever it is run.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_to =   # To
- email_cc =   # CC
- email_from =   # From
- email_replyto =   # Reply to
- email_subject =   # Subject
- email_subscriber_content =   # Message
- email_attachment_paths =   # Attachments (comma separated)

INPUT (input)
    -> Counter
Counter
    SCOPE = Local
    START = 0
    DOMAIN = counter
    CNT_ATTR = _email_feature_id
    -> ParameterFetcher
ParameterFetcher
    ATTR_LIST = _email_from {$(email_from)} _email_replyto {$(email_replyto)} _email_attachment_paths {$(email_attachment_paths)} _email_cc {$(email_cc)}
    -> AttributeCreator
AttributeCreator
    NUM_PRIOR_FEATURES = 0
    NUM_SUBSEQUENT_FEATURES = 0
    ATTR_LIST = _email_to,$(email_to),_email_subject,$(email_subject),_email_subscriber_content,$(email_subscriber_content)
    -> JSONTemplater
JSONTemplater
    RESULT_ATTRIBUTE = text_line_data
    CONSECUTIVE_GROUPS = No
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    VISIBLE_QUERY_VALIDATE = Yes
    -> Tester
Tester
    TEST_MODE = Automatic
    TEST_DESCRIPTION = ""
    BOOL_OP = OR
    TEST_CLAUSE = TEST _email_attachment_paths ATTRIBUTE_IS_EMPTY <Unused>
    PASSED -> OUTPUT (output)
    FAILED -> AttributeSplitter
OUTPUT (output)

Bookmark: Add the attachments
AttributeSplitter
    LIST_NAME = _email_attachment_path_list
    ATTR_NAME = _email_attachment_paths
    DELIMITER = ,
    TRIM_OPTION = Both
    DROP_EMPTY_PARTS = No
    -> ListExploder
ListExploder
    INDEX_ATTR = _element_index
    MODE = List Elements and Original Attributes
    LIST_ATTR = _email_attachment_path_list{}
    LIST_FOUND -> StringConcatenator
StringConcatenator
    PARM_LINE = "email_attachment{@Value(_element_index)}": "@Value(_email_attachment_path_list)"
    VAL_ATTR = _email_attachment_json
    -> Aggregator
Aggregator
    GROUP_BY = _email_feature_id
    MODE = Assemble One Level
    ACCUM_ATTRS_NAME = Yes
    SEP = ,
    AGGREGATE_TYPE = Homogeneous Collection (If Possible)
    CONCAT_ATTRS = _email_attachment_json
    ORDERED = No
    AGGREGATE -> StringReplacer_2
StringReplacer_2
    SRC_ATTRS = _email_attachment_json
    REGEXP = no
    CASE = no
    REPLACE_TEXT = \\
    NO_MATCH = _FME_NO_OP_
    FIND_TEXT = \
    -> StringReplacer
StringReplacer
    SRC_ATTRS = text_line_data
    REGEXP = no
    CASE = no
    REPLACE_TEXT:
      ,
      @Value(_email_attachment_json)
      }
    NO_MATCH = _FME_NO_OP_
    FIND_TEXT = }
    -> OUTPUT (output)
