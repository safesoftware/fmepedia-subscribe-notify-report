FME workspace subscription_request.fmw

Parameters:
- SourceDataset_TEXTLINE = Z:\DonStuff\DemoData\2013Demos\AlertReportingSystem\2ndIteration\data\subscriber_data\subscription_point_request.txt   # Source Text File(s)

Readers:
- TEXTLINE_1: TEXTLINE from $(SourceDataset_TEXTLINE)

Writers:
- GOOGLEFUSIONTABLES_DB_1: GOOGLEFUSIONTABLES_DB

text_line (reader TEXTLINE_1)
    attributes: text_line_data buffer
    -> AttributeTrimmer
AttributeTrimmer
    TRIM_CHARS = "
    TRIM_TO_NONE = Yes
    TRIM_TYPE = Both
    SRC_ATTRS = text_line_data
    -> JSONFlattener
JSONFlattener
    RECURSIVE = Yes
    JSON_ATTR = text_line_data
    -> AttributeExposer
AttributeExposer
    ATTR_LIST = email,wkt,enddate,startdate,twitter,area_type,radius
    -> UUIDGenerator
UUIDGenerator
    UUID_ATTR = request_id
    -> TimeStamper
TimeStamper
    FMT = FME Date/Time (^Y^m^d^H^M^S)
    TIME_ATTR = request_time
    -> SubstringExtractor
SubstringExtractor
    SRC_ATTR = startdate
    END = 9
    START = 0
    RESULT_ATTR = startdate
    -> SubstringExtractor_2
SubstringExtractor_2
    SRC_ATTR = enddate
    END = 9
    START = 0
    RESULT_ATTR = enddate
    -> DateFormatter
DateFormatter
    FMT = XML DateTime (%Y-%m-%dT%H:%M:%S)
    DATE_ATTR = request_time
    -> StringConcatenator
    -> EMSSubscriptionRequest (writer GOOGLEFUSIONTABLES_DB_1)
StringConcatenator
    PARM_LINE:
      {
      email_to:@Value(email),
      email_subject: "Request for FME Server Alerts<REQUEST_ID:@Value(request_id)>",
      subscriber_content: "You  requested to receive notifcation alerts from http://alertdemo.safe.com/subscriber.html at @Value(request_time). \r\n\r\nThe details of the request are as follows: \r\n\r\n email:@Value(email) \r\n\r\n Twitter: @Value(twitter) \r\n\r\n StartDate: @Value(startdate) \r\n\r\n EndDate: @Value(enddate) \r\n\r\n QueryType:@Value(area_type) \r\n\r\nIf this is correct then reply to this email from the email address it was addressed to. \r\n \r\n\r\n DO NOT EDIT \r\n\r\nIf you did not want to be sent alerts then simply ignore this email."
      }
    VAL_ATTR = subscription_request
    -> Logger_3
    -> FMEServerNotifier
FMEServerNotifier
    STATUS_CODE_ATTR = _http_status_code
    URL = http://dondemo.safe.com
    TOPIC = ems_subscribe_confirm_email
    HTTP_UPLOAD_BODY = subscription_request
    HTTP_UPLOAD_CONTENT_TYPE = text/plain
    -> Logger_2
Logger_2 [off]
    MESSAGE = Feature is:
    MAXFEATS = 20
    MAXCOORDS = 20
Logger_3
    MESSAGE = Feature is:
    MAXFEATS = 20
    MAXCOORDS = 20
EMSSubscriptionRequest (writer GOOGLEFUSIONTABLES_DB_1)
    attributes: email text, enddate datetime, request_id text, request_time datetime, startdate datetime, twitter text, wkt text, query_type text, buffer_width number
