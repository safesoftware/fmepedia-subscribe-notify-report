FME workspace subscription_confirm_email.fmw

Parameters:
- SourceDataset_TEXTLINE = Z:\DonStuff\DemoData\2013Demos\AlertReportingSystem\2ndIteration\data\subscriber_data\subscribe_confirm_email.txt   # Source Text File(s)

Readers:
- TEXTLINE_1: TEXTLINE from $(SourceDataset_TEXTLINE)
- GOOGLEFUSIONTABLES_DB_1: GOOGLEFUSIONTABLES_DB

Writers:
- GOOGLEFUSIONTABLES_1: GOOGLEFUSIONTABLES in LL84
- GOOGLEFUSIONTABLES_DB_2: GOOGLEFUSIONTABLES_DB

text_line (reader TEXTLINE_1)
    attributes: text_line_data buffer
    -> JSONFlattener
JSONFlattener
    RECURSIVE = Yes
    JSON_ATTR = text_line_data
    -> AttributeExposer
AttributeExposer
    ATTR_LIST = email_content,email_from,email_received,email_sent,email_subject,email_to
    -> StringSearcher
StringSearcher
    ATTRIBUTE = email_subject
    REGEXP = <REQUEST_ID:.*>
    CASE = no
    MATCHED -> SubstringExtractor
SubstringExtractor
    SRC_ATTR = _matched_characters
    END = -2
    START = 12
    RESULT_ATTR = request_id
    -> InlineQuerier [input 1]
Note: EMSSubscriptionRequest
EMSSubscriptionRequest (reader GOOGLEFUSIONTABLES_DB_1)
    attributes: email text, wkt text, request_id text, request_time text, enddate text, startdate text, twitter text, query_type text, buffer_width number
    -> InlineQuerier [input 2]
InlineQuerier
    QUERY_SCHEMA = Matched,request_id,varchar(30),email_from,varchar(30),subscription_confirmation.fme_feature_content,fme_feature_content,email,varchar(30),subscription_request.fme_feature_content,fme_feature_content
    TABLE_DEF = subscription_confirmation,request_id,varchar(30),email_from,varchar(30),subscription_request,request_id,varchar(30),email,varchar(30)
    QUERY_DEF:
      Matched,SELECT *
      FROM subscription_confirmation,
           subscription_request
      WHERE   subscription_request.email      =  subscription_confirmation. email_from AND
              subscription_request.request_id =  subscription_confirmation.request_id,FIRST
    Matched -> GeometryReplacer
GeometryReplacer
    KIND_LONG = OGC Well Known Text
    ATTR = wkt
    -> Reprojector
Reprojector
    DEST = TX83-C
    SOURCE = EPSG:4326
    RASTER_CELL_SIZE = Preserve Cells
    INTERPOLATION_TYPE_NAME = Nearest Neighbor
    STROKE_ARCS = Yes
    REPROJECTED -> Bufferer_2
Bufferer_2
    BUFFSTYLE = CAP_ROUND
    WIDTH = @Value(buffer_width)
    ANGLE = 22.5
    BUFFERED -> Reprojector_2
Reprojector_2
    DEST = EPSG:4326
    SOURCE = TX83-C
    RASTER_CELL_SIZE = Preserve Cells
    INTERPOLATION_TYPE_NAME = Nearest Neighbor
    STROKE_ARCS = Yes
    REPROJECTED -> BoundingBoxReplacer
Note: Google Fusion Tables only supports bbox query. / Eventually we will use the actual geometry. we need to wait / for GFT round 2.0 from Ryan. That way GFT will do the rough / filtering and FME will do the fine filtering. / See the notification generation for this.
BoundingBoxReplacer
    BOXTYPE = Bounding Box
    BOX -> TimeStamper
TimeStamper
    FMT = FME Date (^Y^m^d)
    TIME_ATTR = current_date
    -> DateFormatter
DateFormatter
    FMT = FME Date (%Y%m%d)
    DATE_ATTR = enddate,startdate
    -> TestFilter
    -> StringConcatenator
StringConcatenator
    PARM_LINE:
      {
      email_to:@Value(email),
      email_subject: "FME Server Alert Service has been activated.<REQUEST_ID:@Value(request_id)>",
      subscriber_content: "You  are now registered to receive notifcation alerts from http://alertdemo.safe.com/subscriber.html at @Value(request_time). \r\n\r\nThe details of the request are as follows: \r\n\r\n email:@Value(email) \r\n\r\n Twitter: @Value(twitter) \r\n\r\n StartDate: @Value(startdate) \r\n\r\n EndDate: @Value(enddate) \r\n\r\n QueryType:@Value(query_type) \r\n \r\n \r\n ----  UNSUBSCRIBE  ----- \r\n\r\nTo unsubscribe to these notifications click the link below. \r\n http://alertdemo.safe.com/fmejobsubmitter/EEMS/subscription_delete.fmw?opt_servicemode=async&subscriber_id=@Value(request_id)&email_address=@Value(email) \r\n"
      }
    VAL_ATTR = subscription_request
    -> FMEServerNotifier
FMEServerNotifier
    STATUS_CODE_ATTR = _http_status_code
    URL = http://localhost
    HTTP_AUTH_PASSWORD = m4ll4rd
    TOPIC = ems_subscribe_activated
    HTTP_AUTH_USERNAME = admin
    HTTP_UPLOAD_BODY = subscription_request
    HTTP_UPLOAD_CONTENT_TYPE = text/plain
TestFilter
    TEST_LIST:
      BOOL_OP,AND,COMPOSITE_TEST,<Unused>,TEST_CLAUSE,"TEST ""@Value(startdate)"" <= ""@Value(current_date)""
      TEST ""@Value(enddate)"" >= ""@Value(current_date)""",Active,BOOL_OP,OR,COMPOSITE_TEST,<Unused>,TEST_CLAUSE,"TEST ""@Value(startdate)"" > ""@Value(current_date)""",Future
    <UNFILTERED> -> Logger
    Active -> EMSActiveSubscriptions (writer GOOGLEFUSIONTABLES_1)
    Active -> EMSExpireSubscriptions (writer GOOGLEFUSIONTABLES_DB_2)
    Future -> EMSFutureSubscriptions (writer GOOGLEFUSIONTABLES_1)
    Future -> EMSExpireSubscriptions (writer GOOGLEFUSIONTABLES_DB_2)
    Future -> EMSSubscriptionRequest (writer GOOGLEFUSIONTABLES_DB_2)
    Active -> EMSSubscriptionRequest (writer GOOGLEFUSIONTABLES_DB_2)
    <UNFILTERED> -> EMSSubscriptionRequest (writer GOOGLEFUSIONTABLES_DB_2)
Note: EMSActiveSubscriptions
EMSActiveSubscriptions (writer GOOGLEFUSIONTABLES_1)
    attributes: email text, enddate datetime, request_id text, request_time datetime, startdate datetime, twitter text, query_type text
Note: EMSFutureSubscriptions
EMSFutureSubscriptions (writer GOOGLEFUSIONTABLES_1)
    attributes: email text, enddate datetime, request_id text, request_time datetime, startdate datetime, twitter text, query_type text
Note: EMSExpireSubscriptions
EMSExpireSubscriptions (writer GOOGLEFUSIONTABLES_DB_2)
    attributes: email text, enddate datetime, request_id text, request_time datetime, startdate datetime, twitter text, query_type text
Note: EMSSubscriptionRequest / Request handled so delete.
EMSSubscriptionRequest (writer GOOGLEFUSIONTABLES_DB_2)
    attributes: email text, wkt text, request_id text, request_time text, enddate text, startdate text, twitter text, query_type text, buffer_width number
Logger
    MESSAGE = Feature is:
    MAXFEATS = 20
    MAXCOORDS = 20
GeometryReplacer_OUTPUT: Inspector [off]
reprojected_point: Inspector [off]
buffered: Inspector [off]
Logger_2 [off]
    MESSAGE = Feature is:
    MAXFEATS = 20
    MAXCOORDS = 20
